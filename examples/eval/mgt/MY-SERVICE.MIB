--
-- This SMIv2 module has been generated by pyang and yang2smi plugin. Do not edit.
--

MYSERVICE-MIB DEFINITIONS ::= BEGIN
    
    IMPORTS
        OBJECT-TYPE,
        NOTIFICATION-TYPE,
        Unsigned32,
        enterprises,
        MODULE-IDENTITY,
        Integer64,
        OBJECT-IDENTITY    FROM SNMPv2-SMI
        NOTIFICATION-GROUP,
        MODULE-COMPLIANCE,
        OBJECT-GROUP    FROM SNMPv2-CONF
        TruthValue,
        TEXTUAL-CONVENTION    FROM SNMPv2-TC;

    myService MODULE-IDENTITY
        LAST-UPDATED "201512221251Z"
        ORGANIZATION
            "OpenClovis Solutions, Inc"

        CONTACT-INFO
            "Andrew Stone <stone@openclovis.com>"

        DESCRIPTION
            "Automagically generated description"


        --Revision History
    ::= { enterprises 99840 }

    subscribersTable OBJECT-TYPE
        SYNTAX    SEQUENCE OF Subscribers
        MAX-ACCESS not-accessible
        STATUS current

        DESCRIPTION
            "Automagically generated description"

        ::= { myService 1 }
    
    subscribers OBJECT-TYPE
        SYNTAX Subscribers
        MAX-ACCESS not-accessible
        STATUS current

        DESCRIPTION
            "This list defines who can use this service"


        INDEX { name }

    ::= { subscribersTable 1 }

        Subscribers ::= SEQUENCE  {
            name    OCTET STRING,
            active    TruthValue,
            level    INTEGER,
            limit    Integer64,
            use    Integer64
        }

    name OBJECT-TYPE
        SYNTAX OCTET STRING (SIZE(1..255))
        MAX-ACCESS read-create
        STATUS current
        DESCRIPTION
            "Automatically  generated description"

        ::= { subscribers 1 }

    active OBJECT-TYPE
        SYNTAX TruthValue
        MAX-ACCESS read-create
        STATUS current
        DESCRIPTION
            "True means this subscriber is in good standing, False means service is off"

        DEFVAL { true }

        ::= { subscribers 2 }

    level OBJECT-TYPE
        SYNTAX INTEGER {
            copper(0),
            silver(1),
            gold(2)
        }
        MAX-ACCESS read-create
        STATUS current
        DESCRIPTION
            "Automatically  generated description"

        ::= { subscribers 3 }

    limit OBJECT-TYPE
        SYNTAX Integer64
        MAX-ACCESS read-create
        STATUS current
        DESCRIPTION
            "How much of the service this subscriber can use"

        DEFVAL { 10000 }

        ::= { subscribers 4 }

    use OBJECT-TYPE
        SYNTAX Integer64
        MAX-ACCESS read-create
        STATUS current
        DESCRIPTION
            "How much of the service this subscriber has used"

        ::= { subscribers 5 }

    serviceCfg OBJECT IDENTIFIER ::= { myService 2 }

        port OBJECT-TYPE
            SYNTAX Unsigned32
            MAX-ACCESS read-create
            STATUS current
            DESCRIPTION
                "What TCP port to listen on"

            DEFVAL { 8000 }

            ::= { serviceCfg 1 }

        homeLocation OBJECT-TYPE
            SYNTAX OCTET STRING (SIZE(1..255))
            MAX-ACCESS read-create
            STATUS current
            DESCRIPTION
                "What directory on the server contains the pages"

            DEFVAL { "/srv/web" }

            ::= { serviceCfg 2 }

    serviceStats OBJECT IDENTIFIER ::= { myService 3 }

        accessCounts OBJECT IDENTIFIER ::= { serviceStats 1 }

        bytesTransmitted OBJECT IDENTIFIER ::= { serviceStats 2 }
END
