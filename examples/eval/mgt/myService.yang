module myService
{
  namespace "http://www.myCompany.com/ns/myService";
  prefix "myService"; 
  import SAFplusTypes { prefix "SAFplusTypes"; }

  // Let's make a structure to track the subscribers to our fictious service:
  list subscribers
  {
    key "name";
    description "This list defines who can use this service";

    leaf name
    {
      type string;
    }
    leaf active
    {
      type boolean;
      description "True means this subscriber is in good standing, False means service is off";
      default true;
    }

    leaf level
    {
      type enumeration
      {
        enum copper
        { 
          value 0;
        }
        enum silver
        { 
          value 1;
        }
        enum gold
        {
          value 2; 
        }
      }
    }

    leaf limit
    {
      description "How much of the service this subscriber can use";
      type int64;
      default 10000;
    }

    leaf use
    {
      description "How much of the service this subscriber has used";
      type int64;
      //config false;  // This would normally not be config but we want to be able to reset this for the sake of the demo
    }
  }

  container serviceCfg
  {
  leaf port
    {
    description "What TCP port to listen on";
    type uint16;
    default 8080;
    }
  leaf homeLocation
    {
    description "What directory on the server contains the pages";
    type string;
    default "/srv/web";
    }
  }

  container serviceStats
  {
    description "Statistics on the use of this service";
    container accessCounts
    {
      description "How much is the service being used";
      SAFplusTypes:c-existing "SAFplus::MgtHistoryStat<int>"; 
      uses SAFplusTypes:intStatistic; 
      config false;
    }
    container bytesTransmitted
    {
      description "How many bytes are transmitted by the service";
      SAFplusTypes:c-existing "SAFplus::MgtHistoryStat<int>"; 
      uses SAFplusTypes:intStatistic; 
      config false;
    }
  }

  rpc reset
  {
    description "Apply the setting changes. If no parameters are specified the current setting are applied, otherwise the passed parameters are applied and the data model is updated with these parameters";
    input
    {
      leaf path
      {
      	description "Location of the 'root' directory of the web server";
      	type string;
      }
      leaf port
      {
      	description "The TCP port this web server should listen on (default is 80)";
      	type uint16;
      }
    }
  }

}
