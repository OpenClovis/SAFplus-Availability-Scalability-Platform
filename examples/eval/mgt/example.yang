module example 
{
  namespace "http://www.openclovis.org/ns/example";
  import SAFplusTypes { prefix "SAFplusTypes"; }
  prefix "example"; 

  // Let's make a structure to track the subscribers to our fictious service:
  list subscribers
  {
    key "name";
    description "";

    leaf name
    {
      type string;
    }
    leaf active
    {
      type boolean;
      description "True means this subscriber is in good standing, False means service is off";
      default true;
    }

    leaf level
    {
      type enumeration
      {
        enum gold
        {
          value 2; 
        }
        enum silver
        { 
          value 1;
        }
        enum copper
        { 
          value 0;
        }
      }
    }

    leaf limit
    {
      description "How much of the service this subscriber can use";
      type int64;
      default 10000;
    }

    leaf use
    {
      description "How much of the service this subscriber has used";
      type int64;
      config true;
      // config false;
      // The application uses this to track and report use, but I want to be able to reset this for demo purposes so make config true;
    }
  }

  container serviceStats
  {
    description "Statistics on the use of this service";
    container accessCounts
    {
      description "How much is the service being used";
      SAFplusTypes:c-existing "SAFplus::MgtHistoryStat<int>"; 
      uses SAFplusTypes:intStatistic; 
      config false;
    }
  }

}

  


}
