module SAFplusTypes
{
    namespace "http://www.openclovis.org/ns/types";
    prefix "SAFplusTypes";

  description "Common types used within the SAFplus management framework.";

  revision 2013-03-12 
  {
    description "Initial type definitions";
  }

    extension settable  
    {
      argument "value";
      description "Selects whether this option can be changed by the management interface.  This overrides the implicit value which is 'true' for config object and 'false' otherwise.";
    }

    extension persistent 
    {
      argument "value";
      description "Selects whether this option is stored to the database.  This overrides the implicit value which is 'true' for config objects and 'false' otherwise.";
    }

    extension replicated 
    {
      argument "value";
      description "Selects whether this option is replicated to the standby.  This overrides the implicit value which is 'true' for config objects and 'false' otherwise.";
    }


    extension c-decl
    {
      argument "declaration";
      description "Jam a C language declaration into this object";
    }

    extension c-type
    {
      argument "declaration";
      description "Override the normal name that would be generated with this name";
    }

    extension c-existing
    {
      argument "name";
      description "This object already exists, and is called 'name' in the code; do not generate code";
    }

    extension alias
    {
      argument "name";
      description "Another name for the same thing";
    }

    extension ui-commonRange
    {
    description "This indicates a reasonable range for sliders.  However, values outside this range are legal.";
    argument "range";
    }

    extension ui-prompt
    {
      argument "query";
    }
    extension ui-group
    {
      argument "name";
    }

    extension atomic;
    extension extensible;  // Generates 2 classes: xxxGenerated and an empty class xxx:public xxxGenerated {}.  You can put your changes in class xxx...

    extension ui-entity
    {
    description "This command indicates that this object is a GUI UML diagram entity.";
    argument "icon";
    }

    extension ui-button
    {
    description "This command designates the button picture for this entity.";
    argument "button";
    }

    extension ui-container
    {
    description "This extension is used in a contained list or leaf-list and describes the relationship between the container and the contained.  1 means the contained can only be in 1 container.  N means the contained can exist in multiple containers.";
    argument "amount";
    }

    extension ui-contained
    {
    description "This extension is used in a contained list or leaf-list and describes the relationship between the container and the contained.  1 means the contained can only be in 1 container.  N means the contained can exist in multiple containers.";
    argument "amount";
    }

    extension instance-type
    {
    argument "type";
    description "If the Yang type is instance-identifier, this extension refines the type so the UI knows exactly what kind of instances are allowed.";
    }

    extension ui-dialog
    {
      argument "title";
      description "This command triggers a sub-window (not necessarily a modal dialog box) that is created for these options.  If the value is 'class <name>' or 'object <name>' this indicates that this subwindow should be instantiated as the custom code denoted by <name>.  All other values are the title of the sub-window."; 
    }

    typedef SaTimeT
    {
      type uint64;
      SAFplusTypes:c-existing "SaTimeT";
      description "A representation of a time interval, specified in milliseconds";
    }
  
    typedef date
      {
	type uint64;
	description "A representation of a date.";
      }

  grouping intStatistic
    {
      SAFplusTypes:c-existing "SAFplus::MgtHistoryStat<int>"; 

      leaf current
      {
        type uint64;
      }
      /* contains a data points indicating data broken into 10 second periods
         for example:
         100 400 300 200 100 <etc>
      */

      leaf history10sec  
      {
        type string; // comma separated list of uint64;
      }
      leaf history1min  
      {
        type string; // comma separated list of uint64;
      }
      leaf history10min  
      {
        type string; // comma separated list of uint64;
      }
      leaf history1hour  
      {
        type string; // comma separated list of uint64;
      }
      leaf history1day  
      {
        type string; // comma separated list of uint64;
      }
      leaf history1week 
      {
        type string; // comma separated list of uint64;
      }
      leaf history4weeks
      {
        type string; // comma separated list of uint64;
      }
    }
  
  grouping decStatistic
    {
      
      leaf current
      {
        type decimal64
	{
	  fraction-digits 17;
	}
      }
      /* contains a data points indicating data broken into 10 second periods
         for example:
         100 400 300 200 100 <etc>
      */

      leaf history10sec  
      {
        type string; // Comma separated list of float
      }
      leaf history1min
      {
        type string; // Comma separated list of float
      }
      leaf history10min  
      {
        type string; // Comma separated list of float
      }
      leaf history1hour  
      {
        type string; // Comma separated list of float
      }
      leaf history1day  
      {
        type string; // Comma separated list of float
      }
      leaf history1week 
      {
        type string; // Comma separated list of float
      }
      leaf history4weeks
      {
        type string; // Comma separated list of float
      }
    }

  grouping ProcessStats
  {
    description "Statistics on processes running in the system";
    container failures       
      {
      SAFplusTypes:c-existing "SAFplus::MgtHistoryStat<int>"; 
      uses intStatistic; 
      }
    container cpuUtilization 
      { 
      SAFplusTypes:c-existing "SAFplus::MgtHistoryStat<float>"; 
      uses decStatistic; 
      }
    container memUtilization 
      { 
      SAFplusTypes:c-existing "SAFplus::MgtHistoryStat<float>"; 
      uses decStatistic; 
      }
    container pageFaults 
      { 
      SAFplusTypes:c-existing "SAFplus::MgtHistoryStat<int>"; 
      uses intStatistic; 
      }
    container numThreads 
      { 
      SAFplusTypes:c-existing "SAFplus::MgtHistoryStat<int>"; 
      uses intStatistic; 
      }
    container residentMem 
      { 
      SAFplusTypes:c-existing "SAFplus::MgtHistoryStat<int>"; 
      uses intStatistic; 
      }

    leaf processState
      {  
      type enumeration
	{
	  enum Running { value 0; }
	  enum Sleeping { value 1; }
	  enum WaitingForDisk { value 2; }
	  enum Zombie { value 3; }
	  enum Stopped { value 4; }
	  enum TracingStop { value 5; }
        }
      }
  }


  grouping sensor
  {
    description "This structure models a physical sensor";
    leaf name { type string; }
    leaf desc { type string; }
    container val 
      { 
      uses intStatistic; 
      SAFplusTypes:c-existing "SAFplus::MgtHistoryStat<int>";
      }
  }


  /* AMF lifecycle control */
  typedef lifecycleState
  {
    type enumeration
    {
      enum start;
      enum idle;
      enum stop;
    }
  }



}
