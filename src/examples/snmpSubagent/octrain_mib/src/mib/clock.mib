TRAIN-MIB DEFINITIONS ::= BEGIN
   --Title: TRAIN MIB
   IMPORTS
   OBJECT-GROUP, NOTIFICATION-GROUP
   FROM SNMPv2-CONF
   Unsigned32, IpAddress,
   MODULE-IDENTITY, OBJECT-TYPE, OBJECT-IDENTITY, NOTIFICATION-TYPE
       FROM SNMPv2-SMI
   DisplayString, RowStatus
       FROM SNMPv2-TC
   enterprises
       FROM RFC1155-SMI;

   ocTrain MODULE-IDENTITY
       LAST-UPDATED        "2007111531Z"
       ORGANIZATION        "OpenClovis"
       CONTACT-INFO        "Technical Support         
               support@openclovis.com"
                           
       DESCRIPTION         "This is the top node of the TRAINING MIB."

       ::= { enterprises 103 }

    
   clockStatus OBJECT IDENTIFIER ::= { ocTrain 1 }

   clockRunningStatus OBJECT-TYPE
       SYNTAX              INTEGER {
                               stopped( 0 ),
                               running( 1 )
                           }
       MAX-ACCESS          read-only
       STATUS              current
       DESCRIPTION         "Indicate whether or not the Clock is running or stopped
                           
                           Default is 0 (stopped)."
       ::= { clockStatus 1 }


   clockRedStatus OBJECT-TYPE
       SYNTAX              INTEGER {
                               nonred ( 0 ),
                               red ( 1 )
                           }
       MAX-ACCESS          read-only
       STATUS              current
       DESCRIPTION         "Indicates current redundancy."
       ::= { clockStatus 2 }

   clockTableOid OBJECT IDENTIFIER ::= { ocTrain 2 }

   clockTable OBJECT-TYPE
       SYNTAX              SEQUENCE OF ClockEntry
       MAX-ACCESS          not-accessible
       STATUS              current
       DESCRIPTION         "Table of Clocks"
       ::= { clockTableOid 1 }

   clockTableEntry OBJECT-TYPE
       SYNTAX              ClockEntry
       MAX-ACCESS          not-accessible
       STATUS              current
       DESCRIPTION         "Defines each row in table"
       INDEX               { clockRow }
       ::= { clockTable 1 }

   ClockEntry ::= SEQUENCE {
       clockRow        INTEGER,
       clockId         INTEGER,
       clockHour       INTEGER,
       clockMinute     INTEGER,
       clockSecond     INTEGER,
       alarmHour       INTEGER,
       alarmMinute     INTEGER,
       alarmReaction   INTEGER,
       alarmSet        INTEGER
   }

   clockRow OBJECT-TYPE
       SYNTAX              INTEGER (0..256)      
       MAX-ACCESS          read-write
       STATUS              current
       DESCRIPTION "Clock table row index" 
       ::= { clockTableEntry 1 }

   clockId OBJECT-TYPE
       SYNTAX              INTEGER 
       MAX-ACCESS          read-write
       STATUS              current
       DESCRIPTION "Clock identifier"
       ::= { clockTableEntry 2 }

   clockHour OBJECT-TYPE
       SYNTAX              INTEGER (0..23)
       MAX-ACCESS          read-only
       STATUS              current
       DESCRIPTION "Clock hour"
       ::= { clockTableEntry 3 }

   clockMinute OBJECT-TYPE
       SYNTAX              INTEGER (0..59)
       MAX-ACCESS          read-only
       STATUS              current
       DESCRIPTION "Clock minute"
       ::= { clockTableEntry 4 }

   clockSecond OBJECT-TYPE
       SYNTAX              INTEGER (0..59)
       MAX-ACCESS          read-only
       STATUS              current
       DESCRIPTION "Clock seconds"
       ::= { clockTableEntry 5 }

   alarmHour OBJECT-TYPE
       SYNTAX              INTEGER (0..23)
       MAX-ACCESS          read-write
       STATUS              current
       DESCRIPTION "hour of Alarm condition"
       ::= { clockTableEntry 6 }

   alarmMinute OBJECT-TYPE
       SYNTAX              INTEGER (0..59)
       MAX-ACCESS          read-write
       STATUS              current
       DESCRIPTION "minutes of Alarm condition"
       ::= { clockTableEntry 7 }

   alarmReaction OBJECT-TYPE
       SYNTAX              INTEGER (0..1)
       MAX-ACCESS          read-write
       STATUS              current
       DESCRIPTION "reaction to Alarm : raise trap(0); kill process(1)"
       ::= { clockTableEntry 8 }

   alarmSet OBJECT-TYPE
       SYNTAX              INTEGER (0..1)
       MAX-ACCESS          read-write
       STATUS              current
       DESCRIPTION "set alarm (1) turn alarm off(0)" 
       ::= { clockTableEntry 9 }

   timeSetTableOid OBJECT IDENTIFIER ::= { ocTrain 3 }

   timeSetTable OBJECT-TYPE
       SYNTAX              SEQUENCE OF TimeSet
       MAX-ACCESS          not-accessible
       STATUS              current
       DESCRIPTION         "Table of Time Set Values"
       ::= { timeSetTableOid 1 }

   timeSetTableEntry OBJECT-TYPE
       SYNTAX              TimeSet
       MAX-ACCESS          not-accessible
       STATUS              current
       DESCRIPTION         "Defines each row in table"
       INDEX               { timeSetRow }
       ::= { timeSetTable 1 }

   TimeSet ::= SEQUENCE {
       timeSetRow        INTEGER,
       timeSetHour       INTEGER,
       timeSetMinute     INTEGER,
       timeSetSecond     INTEGER
   }

   timeSetRow OBJECT-TYPE
       SYNTAX              INTEGER (0..256)      
       MAX-ACCESS          read-write
       STATUS              current
       DESCRIPTION "Clock table row index" 
       ::= { timeSetTableEntry 1 }

   timeSetHour OBJECT-TYPE
       SYNTAX              INTEGER (0..23)
       MAX-ACCESS          write-only
       STATUS              current
       DESCRIPTION "Clock hour"
       ::= { timeSetTableEntry 2 }

   timeSetMinute OBJECT-TYPE
       SYNTAX              INTEGER (0..59)
       MAX-ACCESS          write-only
       STATUS              current
       DESCRIPTION "Clock minute"
       ::= { timeSetTableEntry 3 }

   timeSetSecond OBJECT-TYPE
       SYNTAX              INTEGER (0..59)
       MAX-ACCESS          write-only
       STATUS              current
       DESCRIPTION "Clock seconds"
       ::= { timeSetTableEntry 4 }

   nameTableOid OBJECT IDENTIFIER ::= { ocTrain 4 }

   nameTable OBJECT-TYPE
       SYNTAX              SEQUENCE OF NameTableEntry 
       MAX-ACCESS          not-accessible
       STATUS              current
       DESCRIPTION         "Table that maps symbolic node name to node address"
       ::= { nameTableOid 1 }

   nameTableEntry OBJECT-TYPE
       SYNTAX              NameTableEntry
       MAX-ACCESS          not-accessible
       STATUS              current
       DESCRIPTION         "Defines each row in table"
       INDEX               { nodeAdd}
       ::= { nameTable 1 }

   NameTableEntry ::= SEQUENCE {
       nodeAdd           Unsigned32,
       nodeName          DisplayString,
       nodeIp            IpAddress,
       nodeCreate        RowStatus
   }


   nodeAdd  OBJECT-TYPE
       SYNTAX              Unsigned32 
       MAX-ACCESS          read-create
       STATUS              current
       DESCRIPTION "node address as row index" 
       ::= { nameTableEntry 1 }

   nodeName OBJECT-TYPE
       SYNTAX              DisplayString
       MAX-ACCESS          read-create 
       STATUS              current
       DESCRIPTION "Name of the table" 
       ::= { nameTableEntry 2 }
   nodeIp  OBJECT-TYPE
       SYNTAX              IpAddress 
       MAX-ACCESS          read-create
       STATUS              current
       DESCRIPTION "node IP" 
       ::= { nameTableEntry 3 }
        
   nodeCreate  OBJECT-TYPE
       SYNTAX              RowStatus 
       MAX-ACCESS          read-create
       STATUS              current
       DESCRIPTION "node IP" 
       ::= { nameTableEntry 4 }
   clockNotifications OBJECT IDENTIFIER ::= { ocTrain 5 }

   alarmTrap NOTIFICATION-TYPE
       OBJECTS { clockId }
       STATUS current
       DESCRIPTION "Alarm raised if that is option chosen"
                      ::= {  clockNotifications 1 }

   clockObjectGroup OBJECT IDENTIFIER ::= { ocTrain 6 }

   clockNotifyGroup OBJECT IDENTIFIER ::= { ocTrain 7 }

   clockGroup OBJECT-GROUP
   OBJECTS { 
            clockRunningStatus,
            clockRedStatus,
            clockHour,
            clockSecond,
            clockMinute,
            clockId,
            clockRow,
            alarmHour,
            alarmMinute,  
            alarmReaction
            }
   STATUS  current
   DESCRIPTION "object group"
         ::= {  clockObjectGroup 1}

   clockNotify OBJECT-GROUP
   OBJECTS { clockId }
   STATUS  current
   DESCRIPTION "notify group"
       ::= { clockNotifyGroup 1}


END
