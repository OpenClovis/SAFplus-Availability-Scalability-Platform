/*
 * This module has been generated by smidump 0.4.8:
 *
 *      smidump -f yang ITU-ALARM-TC-MIB
 *
 * Do not edit. Edit the source file instead!
 */

module ITU-ALARM-TC-MIB {

  /*** NAMESPACE / PREFIX DEFINITION ***/

  namespace "urn:ietf:params:xml:ns:yang:smiv2:ITU-ALARM-TC-MIB";
  prefix "itu-alarm";

  /*** LINKAGE (IMPORTS / INCLUDES) ***/


  /*** META INFORMATION ***/

  organization      
   "IETF Distributed Management Working Group";

  contact           
   " WG EMail: disman@ietf.org
    Subscribe: disman-request@ietf.org
    http://www.ietf.org/html.charters/disman-charter.html
    
    Chair:     Randy Presuhn
               randy_presuhn@mindspring.com
    
    Editors:   Sharon Chisholm
               Nortel Networks
               PO Box 3511 Station C
               Ottawa, Ont.  K1Y 4H7
               Canada
               schishol@nortelnetworks.com
    
               Dan Romascanu
               Avaya
               Atidim Technology Park, Bldg. #3
               Tel Aviv, 61131
               Israel
               Tel: +972-3-645-8414
               Email: dromasca@avaya.com";

  description       
   "This MIB module defines the ITU Alarm
    textual convention for objects not expected to require
    regular extension.
    
    Copyright (C) The Internet Society (2004).  The
    initial version of this MIB module was published
    in RFC 3877.  For full legal notices see the RFC
    itself.  Supplementary information may be available on:
    http://www.ietf.org/copyrights/ianamib.html";

  revision "2004-09-09" {
    description     
     "Initial version, published as RFC 3877.";
  }

  /*** TYPE DEFINITIONS ***/

  typedef ItuPerceivedSeverity {
    type enumeration {
      enum cleared       { value 1; }
      enum indeterminate { value 2; }
      enum critical      { value 3; }
      enum major         { value 4; }
      enum minor         { value 5; }
      enum warning       { value 6; }
    }
    description     
     "ITU perceived severity values";
    reference       
     "ITU Recommendation M.3100, 'Generic Network Information
      Model', 1995
      ITU Recommendation X.733, 'Information Technology - Open
      Systems Interconnection - System Management: Alarm
      Reporting Function', 1992";
  }

  typedef ItuTrendIndication {
    type enumeration {
      enum moreSevere { value 1; }
      enum noChange   { value 2; }
      enum lessSevere { value 3; }
    }
    description     
     "ITU trend indication values for alarms.";
    reference       
     "ITU Recommendation M.3100, 'Generic Network Information
      Model', 1995
      ITU Recommendation X.733, 'Information Technology - Open
      Systems Interconnection - System Management: Alarm
      Reporting Function', 1992";
  }

} /* end of module ITU-ALARM-TC-MIB */
