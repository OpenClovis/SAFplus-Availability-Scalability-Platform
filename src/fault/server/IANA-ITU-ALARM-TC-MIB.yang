/*
 * This module has been generated by smidump 0.4.8:
 *
 *      smidump -f yang IANA-ITU-ALARM-TC-MIB
 *
 * Do not edit. Edit the source file instead!
 */

module IANA-ITU-ALARM-TC-MIB {

  /*** NAMESPACE / PREFIX DEFINITION ***/

  namespace "urn:ietf:params:xml:ns:yang:smiv2:IANA-ITU-ALARM-TC-MIB";
  prefix "iana-itu";

  /*** LINKAGE (IMPORTS / INCLUDES) ***/


  /*** META INFORMATION ***/

  organization      
   "IANA";

  contact           
   "Postal:    Internet Assigned Numbers Authority
    Internet Corporation for Assigned Names
    and Numbers
    4676 Admiralty Way, Suite 330
    Marina del Rey, CA 90292-6601
    USA
    
    Tel:    +1  310-823-9358
    E-Mail: iana@iana.org";

  description       
   "The MIB module defines the ITU Alarm
    textual convention for objects expected to require
    regular extension.
    
    Copyright (C) The Internet Society (2004).  The
    initial version of this MIB module was published
    in RFC 3877.  For full legal notices see the RFC
    itself.  Supplementary information may be available on:
    http://www.ietf.org/copyrights/ianamib.html";

  revision "2004-09-09" {
    description     
     "Initial version, published as RFC 3877.";
  }

  /*** TYPE DEFINITIONS ***/

  typedef ProbableCause {
    type enumeration {
      enum aIS                                 { value 1; }
      enum callSetUpFailure                    { value 2; }
      enum degradedSignal                      { value 3; }
      enum farEndReceiverFailure               { value 4; }
      enum framingError                        { value 5; }
      enum lossOfFrame                         { value 6; }
      enum lossOfPointer                       { value 7; }
      enum lossOfSignal                        { value 8; }
      enum payloadTypeMismatch                 { value 9; }
      enum transmissionError                   { value 10; }
      enum remoteAlarmInterface                { value 11; }
      enum excessiveBER                        { value 12; }
      enum pathTraceMismatch                   { value 13; }
      enum unavailable                         { value 14; }
      enum signalLabelMismatch                 { value 15; }
      enum lossOfMultiFrame                    { value 16; }
      enum receiveFailure                      { value 17; }
      enum transmitFailure                     { value 18; }
      enum modulationFailure                   { value 19; }
      enum demodulationFailure                 { value 20; }
      enum broadcastChannelFailure             { value 21; }
      enum connectionEstablishmentError        { value 22; }
      enum invalidMessageReceived              { value 23; }
      enum localNodeTransmissionError          { value 24; }
      enum remoteNodeTransmissionError         { value 25; }
      enum routingFailure                      { value 26; }
      enum backplaneFailure                    { value 51; }
      enum dataSetProblem                      { value 52; }
      enum equipmentIdentifierDuplication      { value 53; }
      enum externalIFDeviceProblem             { value 54; }
      enum lineCardProblem                     { value 55; }
      enum multiplexerProblem                  { value 56; }
      enum nEIdentifierDuplication             { value 57; }
      enum powerProblem                        { value 58; }
      enum processorProblem                    { value 59; }
      enum protectionPathFailure               { value 60; }
      enum receiverFailure                     { value 61; }
      enum replaceableUnitMissing              { value 62; }
      enum replaceableUnitTypeMismatch         { value 63; }
      enum synchronizationSourceMismatch       { value 64; }
      enum terminalProblem                     { value 65; }
      enum timingProblem                       { value 66; }
      enum transmitterFailure                  { value 67; }
      enum trunkCardProblem                    { value 68; }
      enum replaceableUnitProblem              { value 69; }
      enum realTimeClockFailure                { value 70; }
      enum antennaFailure                      { value 71; }
      enum batteryChargingFailure              { value 72; }
      enum diskFailure                         { value 73; }
      enum frequencyHoppingFailure             { value 74; }
      enum iODeviceError                       { value 75; }
      enum lossOfSynchronisation               { value 76; }
      enum lossOfRedundancy                    { value 77; }
      enum powerSupplyFailure                  { value 78; }
      enum signalQualityEvaluationFailure      { value 79; }
      enum tranceiverFailure                   { value 80; }
      enum protectionMechanismFailure          { value 81; }
      enum protectingResourceFailure           { value 82; }
      enum airCompressorFailure                { value 101; }
      enum airConditioningFailure              { value 102; }
      enum airDryerFailure                     { value 103; }
      enum batteryDischarging                  { value 104; }
      enum batteryFailure                      { value 105; }
      enum commercialPowerFailure              { value 106; }
      enum coolingFanFailure                   { value 107; }
      enum engineFailure                       { value 108; }
      enum fireDetectorFailure                 { value 109; }
      enum fuseFailure                         { value 110; }
      enum generatorFailure                    { value 111; }
      enum lowBatteryThreshold                 { value 112; }
      enum pumpFailure                         { value 113; }
      enum rectifierFailure                    { value 114; }
      enum rectifierHighVoltage                { value 115; }
      enum rectifierLowFVoltage                { value 116; }
      enum ventilationsSystemFailure           { value 117; }
      enum enclosureDoorOpen                   { value 118; }
      enum explosiveGas                        { value 119; }
      enum fire                                { value 120; }
      enum flood                               { value 121; }
      enum highHumidity                        { value 122; }
      enum highTemperature                     { value 123; }
      enum highWind                            { value 124; }
      enum iceBuildUp                          { value 125; }
      enum intrusionDetection                  { value 126; }
      enum lowFuel                             { value 127; }
      enum lowHumidity                         { value 128; }
      enum lowCablePressure                    { value 129; }
      enum lowTemperatue                       { value 130; }
      enum lowWater                            { value 131; }
      enum smoke                               { value 132; }
      enum toxicGas                            { value 133; }
      enum coolingSystemFailure                { value 134; }
      enum externalEquipmentFailure            { value 135; }
      enum externalPointFailure                { value 136; }
      enum storageCapacityProblem              { value 151; }
      enum memoryMismatch                      { value 152; }
      enum corruptData                         { value 153; }
      enum outOfCPUCycles                      { value 154; }
      enum sfwrEnvironmentProblem              { value 155; }
      enum sfwrDownloadFailure                 { value 156; }
      enum lossOfRealTimel                     { value 157; }
      enum applicationSubsystemFailure         { value 158; }
      enum configurationOrCustomisationError   { value 159; }
      enum databaseInconsistency               { value 160; }
      enum fileError                           { value 161; }
      enum outOfMemory                         { value 162; }
      enum softwareError                       { value 163; }
      enum timeoutExpired                      { value 164; }
      enum underlayingResourceUnavailable      { value 165; }
      enum versionMismatch                     { value 166; }
      enum bandwidthReduced                    { value 201; }
      enum congestion                          { value 202; }
      enum excessiveErrorRate                  { value 203; }
      enum excessiveResponseTime               { value 204; }
      enum excessiveRetransmissionRate         { value 205; }
      enum reducedLoggingCapability            { value 206; }
      enum systemResourcesOverload             { value 207; }
      enum adapterError                        { value 500; }
      enum applicationSubsystemFailture        { value 501; }
      enum bandwidthReducedX733                { value 502; }
      enum callEstablishmentError              { value 503; }
      enum communicationsProtocolError         { value 504; }
      enum communicationsSubsystemFailure      { value 505; }
      enum configurationOrCustomizationError   { value 506; }
      enum congestionX733                      { value 507; }
      enum coruptData                          { value 508; }
      enum cpuCyclesLimitExceeded              { value 509; }
      enum dataSetOrModemError                 { value 510; }
      enum degradedSignalX733                  { value 511; }
      enum dteDceInterfaceError                { value 512; }
      enum enclosureDoorOpenX733               { value 513; }
      enum equipmentMalfunction                { value 514; }
      enum excessiveVibration                  { value 515; }
      enum fileErrorX733                       { value 516; }
      enum fireDetected                        { value 517; }
      enum framingErrorX733                    { value 518; }
      enum heatingVentCoolingSystemProblem     { value 519; }
      enum humidityUnacceptable                { value 520; }
      enum inputOutputDeviceError              { value 521; }
      enum inputDeviceError                    { value 522; }
      enum lanError                            { value 523; }
      enum leakDetected                        { value 524; }
      enum localNodeTransmissionErrorX733      { value 525; }
      enum lossOfFrameX733                     { value 526; }
      enum lossOfSignalX733                    { value 527; }
      enum materialSupplyExhausted             { value 528; }
      enum multiplexerProblemX733              { value 529; }
      enum outOfMemoryX733                     { value 530; }
      enum ouputDeviceError                    { value 531; }
      enum performanceDegraded                 { value 532; }
      enum powerProblems                       { value 533; }
      enum pressureUnacceptable                { value 534; }
      enum processorProblems                   { value 535; }
      enum pumpFailureX733                     { value 536; }
      enum queueSizeExceeded                   { value 537; }
      enum receiveFailureX733                  { value 538; }
      enum receiverFailureX733                 { value 539; }
      enum remoteNodeTransmissionErrorX733     { value 540; }
      enum resourceAtOrNearingCapacity         { value 541; }
      enum responseTimeExecessive              { value 542; }
      enum retransmissionRateExcessive         { value 543; }
      enum softwareErrorX733                   { value 544; }
      enum softwareProgramAbnormallyTerminated { value 545; }
      enum softwareProgramError                { value 546; }
      enum storageCapacityProblemX733          { value 547; }
      enum temperatureUnacceptable             { value 548; }
      enum thresholdCrossed                    { value 549; }
      enum timingProblemX733                   { value 550; }
      enum toxicLeakDetected                   { value 551; }
      enum transmitFailureX733                 { value 552; }
      enum transmiterFailure                   { value 553; }
      enum underlyingResourceUnavailable       { value 554; }
      enum versionMismatchX733                 { value 555; }
      enum authenticationFailure               { value 600; }
      enum breachOfConfidentiality             { value 601; }
      enum cableTamper                         { value 602; }
      enum delayedInformation                  { value 603; }
      enum denialOfService                     { value 604; }
      enum duplicateInformation                { value 605; }
      enum informationMissing                  { value 606; }
      enum informationModificationDetected     { value 607; }
      enum informationOutOfSequence            { value 608; }
      enum keyExpired                          { value 609; }
      enum nonRepudiationFailure               { value 610; }
      enum outOfHoursActivity                  { value 611; }
      enum outOfService                        { value 612; }
      enum proceduralError                     { value 613; }
      enum unauthorizedAccessAttempt           { value 614; }
      enum unexpectedInformation               { value 615; }
      enum other                               { value 1024; }
    }
    description     
     "ITU-T probable cause values.  Duplicate values defined in
      X.733 are appended with X733 to ensure syntactic uniqueness.
      Probable cause value 0 is reserved for special purposes.
      
      The Internet Assigned Number Authority (IANA) is responsible
      for the assignment of the enumerations in this TC.
      IANAItuProbableCause value of 0 is reserved for special
      purposes and MUST NOT be assigned.
      
      Values of IANAItuProbableCause in the range 1 to 1023 are
      reserved for causes that correspond to ITU-T probable cause.
      
      All other requests for new causes will be handled on a
      first-come, first served basis and will be assigned
      enumeration values starting with 1025.
      
      Request should  come in the form of well-formed
      
      
      SMI [RFC2578] for enumeration names that are unique and
      sufficiently descriptive.
      
      While some effort will be taken to ensure that new probable
      causes do not conceptually duplicate existing probable
      causes it is acknowledged that the existence of conceptual
      duplicates in the starting probable cause list is an known
      industry reality.
      
      To aid IANA in the administration of probable cause names
      and values, the OPS Area Director will appoint one or more
      experts to help review requests.
      
      See http://www.iana.org";
    reference       
     "ITU Recommendation M.3100, 'Generic Network Information
      Model', 1995
      ITU Recommendation X.733, 'Information Technology - Open
      Systems Interconnection - System Management: Alarm
      Reporting Function', 1992
      ITU Recommendation X.736, 'Information Technology - Open
      Systems Interconnection - System Management: Security
      Alarm Reporting Function', 1992";
  }

  typedef IANAItuEventType {
    type enumeration {
      enum other                               { value 1; }
      enum communicationsAlarm                 { value 2; }
      enum qualityOfServiceAlarm               { value 3; }
      enum processingErrorAlarm                { value 4; }
      enum equipmentAlarm                      { value 5; }
      enum environmentalAlarm                  { value 6; }
      enum integrityViolation                  { value 7; }
      enum operationalViolation                { value 8; }
      enum physicalViolation                   { value 9; }
      enum securityServiceOrMechanismViolation { value 10; }
      enum timeDomainViolation                 { value 11; }
    }
    description     
     "The ITU event Type values.
      
      The Internet Assigned Number Authority (IANA) is
      responsible for the assignment of the enumerations
      in this TC.
      
      Request should  come in the form of well-formed
      SMI [RFC2578] for enumeration names that are unique
      and sufficiently descriptive.
      
      See http://www.iana.org ";
    reference       
     "ITU Recommendation X.736, 'Information Technology - Open
      Systems Interconnection - System Management: Security
      Alarm Reporting Function', 1992";
  }

} /* end of module IANA-ITU-ALARM-TC-MIB */
