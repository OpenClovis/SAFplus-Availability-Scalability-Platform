module unitTest 
{
  namespace "http://www.openclovis.org/ns/unitTest";
  prefix "ut";
  list Component
  {
    key "name";

    leaf name
    {
      type string;
    }
    leaf id
    {
      type uint32;
    }
    leaf data
    {
      type int64;
    }
    leaf key
    {
      type uint32;
    }
  } 
}
