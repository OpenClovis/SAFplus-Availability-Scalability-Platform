module rpcTest 
{

  namespace "http://www.openclovis.org/ns/rpcTest";
  prefix "rpc";

  organization
    "OpenClovis Solutions, Inc";

  contact
    "Andrew Stone <stone@openclovis.com>";

  description
    "Test the SAFplus code generation with different yang file definitions.";

  revision 2014-05-30 
  {
    description "Initial description";
    reference "";
  }

  rpc testGetRpcMethod
  {
    input 
    {
      leaf name
      {
        type string;
      }
    }
    
    output
    {
      container dataResult
      {
        leaf name
        {
          type string;
        }
        leaf status
        {
          type int32;
        }
      }
    }
  }
  
    rpc testGetRpcMethod2
  {
    input 
    {
      leaf name
      {
        type string;
      }
    }
    
    output
    {
      container dataResult
      {
        leaf name
        {
          type string;
        }
        leaf status
        {
          type int32;
        }
      }
    }
  }


  rpc testGetRpcMethod3
  {
    input 
    {
      leaf name
      {
        type string;
      }
    }
    
    output
    {
      container dataResult
      {
        leaf name
        {
          type string;
        }
        leaf status
        {
          type int32;
        }
      }
    }
  }
  
rpc workOperation
    {
      input
      {
    leaf invocation
    {
      type uint64;
    }
    leaf componentName  // Or should I use the component handle?
    {
      type string;
    }
    leaf-list componentHandle
    {
      type binary
            { 
        length 16;  // 2 64-bit words 
        }
    }
    
    leaf operation  // SaAmfHAStateT extended by remove
    {
      type uint32;
    }
    leaf target  // SA_AMF_CSI_ADD_ONE, SA_AMF_CSI_TARGET_ONE, SA_AMF_CSI_TARGET_ALL
    {
      type uint32;
    }

    list keyValuePairs
      {
        leaf theKey
          {
        type string;
          }
        leaf theValue
          {
        type string;
          }
      }
      }
    }
    

  rpc workOperationResponse  // Actually going from the app to the AMF
    {
      input
    {
      leaf invocation
        {
          type uint64;
        }
      leaf result
        {
          type uint32;
        }
    }
    }
  
  
}
