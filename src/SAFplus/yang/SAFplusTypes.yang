module SAFplusTypes
{
    namespace "http://www.openclovis.org/ns/types";
    prefix "safplustypes";

  description "Common types used within the SAFplus management framework.";

  revision 2013-03-12 
  {
    description "Initial type definitions";
  }


    extension c-decl
    {
      argument "declaration";
      description "Jam a C language declaration into this object";
    }

    extension c-type
    {
      argument "declaration";
      description "Override the normal type that would be generated with this type";
    }

    extension c-existing
    {
      argument "name";
      description "This object already exists, and is called 'name' in the code; do not generate code";
    }

    extension alias
    {
      argument "name";
      description "Another name for the same thing";
    }

    extension ui-prompt
    {
      argument "query";
    }
    extension ui-group
    {
      argument "name";
    }

    extension atomic;
    extension extensible;  // Generates 2 classes: xxxGenerated and an empty class xxx:public xxxGenerated {}.  You can put your changes in class xxx...

    extension ui-entity
    {
    description "This command indicates that this object is a GUI UML diagram entity.";
    argument "icon";
    }

    extension ui-button
    {
    description "This command designates the button picture for this entity.";
    argument "button";
    }

    extension ui-container
    {
    description "This extension is used in a contained list or leaf-list and describes the relationship between the container and the contained.  1 means the contained can only be in 1 container.  N means the contained can exist in multiple containers.";
    argument "amount";
    }

    extension ui-contained
    {
    description "This extension is used in a contained list or leaf-list and describes the relationship between the container and the contained.  1 means the contained can only be in 1 container.  N means the contained can exist in multiple containers.";
    argument "amount";
    }

    extension instance-type
    {
    argument "type";
    description "If the Yang type is instance-identifier, this extension refines the type so the UI knows exactly what kind of instances are allowed.";
    }

    extension ui-dialog
    {
      argument "title";
      description "This command triggers a sub-window (not necessarily a modal dialog box) that is created for these options.  If the value is 'class <name>' or 'object <name>' this indicates that this subwindow should be instantiated as the custom code denoted by <name>.  All other values are the title of the sub-window."; 
    }

    typedef SaTimeT
    {
      type uint64;
      safplustypes:c-existing "SaTimeT";
      description "A representation of a time interval, specified in milliseconds";
    }
  
    typedef date
      {
	type uint64;
	description "A representation of a date.";
      }

  grouping intStatistic
    {
      
      leaf current
      {
        type uint64;
      }
      /* contains a data points indicating data broken into 10 second periods
         for example:
         100 400 300 200 100 <etc>
      */

      leaf-list history10sec  
      {
        type uint64;
      }
      leaf-list history1min  
      {
        type uint64;
      }
      leaf-list history10min  
      {
        type uint64;
      }
      leaf-list history1hour  
      {
        type uint64;
      }
      leaf-list history12hour  
      {
        type uint64;
      }
      leaf-list history1day  
      {
        type uint64;
      }
      leaf-list history1week 
      {
        type uint64;
      }
      leaf-list history1month
      {
        type uint64;
      }
    }
  
  grouping decStatistic
    {
      
      leaf current
      {
        type decimal64
	{
	  fraction-digits 17;
	}
      }
      /* contains a data points indicating data broken into 10 second periods
         for example:
         100 400 300 200 100 <etc>
      */

      leaf-list history10sec  
      {
        type decimal64
	{
	  fraction-digits 17;
	}
      }
      leaf-list history1min
      {
        type decimal64
	{
	  fraction-digits 17;
	}
      }
      leaf-list history10min  
      {
        type decimal64
	{
	  fraction-digits 17;
	}
      }
      leaf-list history1hour  
      {
        type decimal64
	{
	  fraction-digits 17;
	}
      }
      leaf-list history12hour  
      {
        type decimal64
	{
	  fraction-digits 17;
	}
      }
      leaf-list history1day  
      {
        type decimal64
	{
	  fraction-digits 17;
	}
      }
      leaf-list history1week 
      {
        type decimal64
	{
	  fraction-digits 17;
	}
      }
      leaf-list history1month
      {
        type decimal64
	{
	  fraction-digits 17;
	}
      }
    }

  grouping processStats
  {
    description "Statistics on processes running in the system";
    container failures       { uses intStatistic; }
    container cpuUtilization { uses decStatistic; }
    container memUtilization { uses decStatistic; }
  }


  grouping sensor
  {
    description "This structure models a physical sensor";
    leaf name { type string; }
    leaf desc { type string; }
    container val { uses intStatistic; }
  }


  /* AMF lifecycle control */
  typedef lifecycleState
  {
    type enumeration
    {
      enum start;
      enum idle;
      enum stop;
    }
  }



}
