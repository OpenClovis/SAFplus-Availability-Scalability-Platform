module safplustypes_module
{
    namespace "http://www.openclovis.org/ns/types";
    prefix "types";
    import ietf-yang-types { prefix yt; }

  description "Common types used within the SAFplus management framework.";

  revision 2013-03-12 
  {
    description "Initial type definitions";
  }


  grouping intStatistic
    {
      
      leaf current
      {
        type uint64;
      }
      /* contains a data points indicating data broken into 10 second periods
         for example:
         100 400 300 200 100 <etc>
      */

      leaf-list history10sec  
      {
        type uint64;
      }
      leaf-list history1min  
      {
        type uint64;
      }
      leaf-list history10min  
      {
        type uint64;
      }
      leaf-list history1hour  
      {
        type uint64;
      }
      leaf-list history12hour  
      {
        type uint64;
      }
      leaf-list history1day  
      {
        type uint64;
      }
      leaf-list history1week 
      {
        type uint64;
      }
      leaf-list history1month
      {
        type uint64;
      }
    }
  
  grouping decStatistic
    {
      
      leaf current
      {
        type decimal64
	{
	  fraction-digits 17;
	}
      }
      /* contains a data points indicating data broken into 10 second periods
         for example:
         100 400 300 200 100 <etc>
      */

      leaf-list history10sec  
      {
        type decimal64
	{
	  fraction-digits 17;
	}
      }
      leaf-list history1min
      {
        type decimal64
	{
	  fraction-digits 17;
	}
      }
      leaf-list history10min  
      {
        type decimal64
	{
	  fraction-digits 17;
	}
      }
      leaf-list history1hour  
      {
        type decimal64
	{
	  fraction-digits 17;
	}
      }
      leaf-list history12hour  
      {
        type decimal64
	{
	  fraction-digits 17;
	}
      }
      leaf-list history1day  
      {
        type decimal64
	{
	  fraction-digits 17;
	}
      }
      leaf-list history1week 
      {
        type decimal64
	{
	  fraction-digits 17;
	}
      }
      leaf-list history1month
      {
        type decimal64
	{
	  fraction-digits 17;
	}
      }
    }

  grouping processStats
  {
    description "Statistics on processes running in the system";
    container failures       { uses intStatistic; }
    container cpuUtilization { uses decStatistic; }
    container memUtilization { uses decStatistic; }
  }


  grouping sensor
  {
    description "This structure models a physical sensor";
    leaf name { type string; }
    leaf desc { type string; }
    container val { uses intStatistic; }
  }


  /* AMF lifecycle control */
  typedef lifecycleState
  {
    type enumeration
    {
      enum start;
      enum idle;
      enum stop;
    }
  }

  /* AMF objects */
  grouping node
  {
    description "A node is a FRU that contains at least one processor and is part of the cluster";
    leaf name { type string; description "SAF node name"; }    
    leaf slot { type int32; description "physical slot number"; }
    leaf FRU  { type yt:xpath1.0; description "link to the physical details of this entity"; }
    
    /* Knobs and dials */
    leaf adminState 
    { 
      type lifecycleState;
      description "Get or set the administrative state of this entity";
    }
    leaf operState
    {
      type lifecycleState;
      description "The current state of this entity";
    }

    leaf identityLedState
    {
      type boolean;
      description "Get/set the state of the identity LED. True is ON, False OFF";
    }

    leaf powerState
    {
      type boolean;
      description "Get/set the power state of this entity. True is ON, False OFF";
    }

    /* Statistics */
    uses processStats;

    list sensors
    {
      key "name";
      uses sensor;
    }
  }

  grouping workAssignment
  {
    leaf name { type string; description "SAF Service Instance name"; }    
    list provisioning
    {
      key name;
      leaf name { type string; description "provisioning keyword"; }    
      leaf val  { type string; description "provisioning value"; }        
    }
  }

  grouping application
  {
    leaf name { type string; description "SAF Service Group name"; }
    leaf ref  { type yt:xpath1.0; description "Link to this applications management area (a custom yang module that may be provided by this application)"; }

    list workAssignments
    {
      key "name";
      uses workAssignment;
    }

    list processes
    {
      key "name";
      leaf name { type string; description "The SAF Components the comprise this Service Group"; }
      leaf ref  { type yt:xpath1.0; description "link to this entity"; }
    }

    /* TODO: AMF SG state and redundancy model here */
    /* Knobs and dials */
    leaf adminState 
    { 
      type lifecycleState;
      description "Get or set the administrative state of this entity";
    }
    
  }

grouping process
  {
    description "Information on processes running in the system";
    leaf name    { type string; description "The SAF Component name"; }
    leaf node    { type string; description "The SAF Node this process is running on"; }
    leaf pid     { type uint32; description "The Linux process id (pid)"; }
    leaf application { type string; description "SAF Service Group that owns this Component"; }
    /* TODO: AMF component state here */

    /* Knobs and dials */
    leaf adminState 
    { 
      type lifecycleState;
      description "Get or set the administrative state of this entity";
    }

    uses processStats;
  }


}
