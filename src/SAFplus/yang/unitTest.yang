module unitTest 
{
  namespace "http://www.openclovis.org/ns/unitTest";
  prefix "ut"; 

  list TestUncontained
  {
    key "name";
    description "";

    leaf name
    {
      type string;
    }
    leaf data
    {
      type int64;
    }
  }
  
  list TestMultiKey
  {
    key "studentName studentCode";
    description "Students' profile";

    leaf studentName
    {
      type string;
    }
    leaf studentCode
    {
      type uint32;
    }
    leaf data
    {
      type int64;
    }
  }
}
