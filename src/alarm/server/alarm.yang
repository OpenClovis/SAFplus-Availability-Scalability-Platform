//  To generate code use: pyang -f y2cpp alarm.yang --y2cpp-output alarmtype --y2cpp-sdkdir ../../../src

module SAFplusAlarm
{
namespace "http://www.openclovis.org/ns/amf";
  prefix "SAFplusAlarm";
  import SAFplusTypes { prefix "SAFplusTypes"; }
  
  organization
        "OpenClovis Solutions, Inc";
   
  contact
        "Andrew Stone <stone@openclovis.com>";

  description
        "Configuration and Statistics for the SAFplus Availability Management Service.  This document is released under the GNU 	General Public License V2.0 or OpenClovis Commerical license.";

  revision 2017-05-15 
    {
        description "Initial description";
        reference "Note, some of the description text is sourced from the Service Availability Forum Application Interface 		Specification document https://tools.ietf.org/html/draft-vallin-alarm-yang-module-00.";
    }

 identity alarm-identity {
       description
         "Base identity for alarm types.  A unique identification of the
          alarm, not including the resource.  Different resources can
          share alarm types.  If the resource reports the same alarm
          type, it is to be considered to be the same alarm.  The alarm
          type is a simplification of the different X.733 and 3GPP alarm
          IRP alarm correlation mechanisms and it allows for
          hierarchical extensions.

          A string-based qualifier can be used in addition to the
          identity in order to have different alarm types based on
          information not known at design-time, such as values in
          textual SNMP Notification var-binds.

          Standards and vendors can define sub-identities to clearly
          identify specific alarm types.

          This identity is abstract and shall not be used for alarms.";
     }

    typedef alarm-severity  {
       type enumeration {
         enum INVALID {
           value 0;
           description
             "Indicates that the severity level could not be
              determined. This level SHOULD be avoided.";
         }
         enum CLEAR {
           value 1;
           description
             "The Cleared severity level indicates the clearing of one or more previously reported alarms. This
              alarm clears all alarms for this managed object that have the same Alarm type, Probable cause and
              Specific problems (if given). (@ref ITU X.733)ot be
              determined. This level SHOULD be avoided.";
         }
	 enum WARNING {
           value 2;
           description
             "The 'warning' severity level indicates the detection of
              a potential or impending service affecting fault, before
              any significant effects have been felt. Action should be
              taken to further diagnose (if necessary) and correct the
              problem in order to prevent it from becoming a more
              serious service affecting fault.";
         }
         enum MINOR {
           value 3;
           description
             "The 'minor' severity level indicates the existence of a
              non-service affecting fault condition and that corrective
              action should be taken in order to prevent a more serious
              (for example, service affecting) fault. Such a severity
              can be reported, for example, when the detected alarm
              condition is not currently degrading the capacity of the
              resource.";
         }
         
         enum MAJOR {
           value 4;
           description
             "The 'major' severity level indicates that a service
              affecting condition has developed and an urgent
              corrective action is required. Such a severity can be
              reported, for example, when there is a severe
              degradation in the capability of the resource
              and its full capability must be restored.";
         }
         enum CRITICAL {
           value 5;
           description
             "The 'critical' severity level indicates that a service
              affecting condition has occurred and an immediate
              corrective action is required. Such a severity can be
              reported, for example, when a resource becomes totally
              out of service and its capability must be restored.";
         }
       }
       description
         "The severity level of the alarm.";
       reference
         "ITU Recommendation X.733, 'Information Technology - Open
            Systems Interconnection - System Management: Alarm Reporting
            Function', 1992";
     }

    typedef timer-type  {
       type enumeration {
         enum INVALID {
           value 0;
           description
             "Indicates that timer could not be
              determined. This level SHOULD be avoided.";
         }
         enum ASSERT {
           value 1;
           description
             "ASSERT Timer Status";
         }
	     enum CLEAR {
           value 2;
           description
             "CLEAR Timer Status";
         }
         }
       description
         "The alarm timer type.";
     }

    typedef operator-state  {
       type enumeration {
         enum NONE {
           value 0;
           description
             "The alarm is not being taken care of.";
         }
         enum ACK {
           value 1;
           description
             "The alarm is being taken care of.  Corrective action not
              taken yet, or failed";
         }
         enum CLOSED {
           value 2;
           description
             "Corrective action taken successfully.";
         }
       }
       description
         "Operator states on an alarm.  The 'closed' state indicates
          that an operator considers the alarm being resolved.  This
          is separate from the resource alarm clear flag.";
     }

     typedef alarm-message-type  {
       type enumeration {
         enum MSG_UNDEFINED {
           value 0;
           description
             "The alarm is not being taken care of.";
         }
         enum MSG_ENTITY_ALARM {
           value 1;
           description
             "The alarm is raised/clear";
         }
         enum MSG_CREATE_PROFILE_ALARM {
           value 2;
           description
             "The alarm profile is created";
         }
         enum MSG_DELETE_PROFILE_ALARM {
           value 3;
           description
             "The alarm profile is delete";
         }
       }
       description
         "Operator states on an alarm.  The 'closed' state indicates
          that an operator considers the alarm being resolved.  This
          is separate from the resource alarm clear flag.";
     }

     typedef alarm-state  {
         type enumeration {
         enum INVALID {
           value 0;
           description
             "The alarm is not indeterminate";
         }
         enum CLEAR {
           value 1;
           description
             "The alarm condition has cleared.";
         }
       enum SUPPRESSED {
           value 2;
           description
             "The alarm state is suppressed.";
         }
       enum ASSERT_UNDER_SOAKING {
           value 3;
           description
             "The alarm state is assert under soaking.";
         }
       enum CLEAR_UNDER_SOAKING {
           value 4;
           description
             "The alarm state is clear under soaking.";
         }
       enum ASSERT {
           value 5;
           description
             "The alarm condition has occured.";
         }
  
       }
       description
         "Operator states on an alarm.  The 'closed' state indicates
          that an operator considers the alarm being resolved.  This
          is separate from the resource alarm clear flag.";
     }

     typedef alarm-category  {
       type enumeration {
         enum INVALID {
          value 1;
           description
             "";
         }
         enum COMMUNICATIONS {
           value 2;
           description
             "An alarm of this type is principally associated with the
              procedures and/or processes required to convey
              information from one point to another";
         }
         enum QUALITYOFSERVICE {
           value 3;
           description
             "An alarm of this type is principally associated with a
              degradation in the quality of a service";
         }
         enum PROCESSINGERROR {
           value 4;
           description
             "An alarm of this type is principally associated with a
              software or processing fault";
         }
         enum EQUIPMENT {
           value 5;
           description
             "An alarm of this type is principally associated with an
              equipment fault";
         }
         enum ENVIROMENTAL {
           value 6;
           description
             "An alarm of this type is principally associated with a
             condition relating to an enclosure in which the equipment
             resides.";
         }
       }
       description
         "The event types as defined by X.733. The use of the term
          'event' is a bit confusing. In an alarm context these are
          top level alarm types.";
       reference
         "ITU Recommendation X.736, 'Information Technology - Open
          Systems Interconnection - System Management: Security
          Alarm Reporting Function', 1992";
     }

    // This enumeration defines all the probable causes of the alarm based on the categories.
     typedef alarm-probable-cause {
       type enumeration {
         enum INVALID {
          value 0;
           description
             "Invalid";
         }
         enum LOSS_OF_SIGNAL {
           value 1;
           description
             "An error condition when there is no data in the communication channel.";
         }
	 enum LOSS_OF_FRAME {
           value 2;
           description
             "An inability to locate the information in bit-delimiters.";
         }
         enum FRAMING_ERROR {
           value 3;
           description
             "Error in the bit-groups delimiters within the bit-stream.";
         }
         enum LOCAL_NODE_TRANSMISSION_ERROR {
           value 4;
           description
             "An error has occured in the transmission between local node and adjacent node.";
         }
         enum REMOTE_NODE_TRANSMISSION_ERROR {
           value 5;
           description
             "An error has occurred on the transmission channel beyond the adjacent node.";
         }
	enum CALL_ESTABLISHMENT_ERROR {
           value 6;
           description
             "Error occured while establishing the connection.";
         }
         enum DEGRADED_SIGNAL {
           value 7;
           description
             "The quality of the singal has decreased.";
         }
         enum SUBSYSTEM_FAILURE {
           value 8;
           description
             "A failure in the subsystem which supports communication over telecommunication links.";
         }
         enum PROTOCOL_ERROR {
           value 9;
           description
             "The communication protocol has been voilated.";
         }
         enum LAN_ERROR {
           value 10;
           description
             "Problem detected in the local area network.";
         }
         enum DTE {
           value 11;
           description
             "Probable cause of the alarm is data transmission error.";
         }
	 enum RESPONSE_TIME_EXCESSIVE {
           value 12;
           description
             "The time delays between the query and its result is beyond the allowable limits.";
         }
         enum QUEUE_SIZE_EXCEEDED {
           value 13;
           description
             "The number of items to be processed has exceeded the specified limits.";
         }
	 enum BANDWIDTH_REDUCED {
           value 14;
           description
             "The bandwidth available for transmission has reduced.";
         }
         enum RETRANSMISSION_RATE_EXCESSIVE {
           value 15;
           description
             "Number of repeat transmission is beyond the allowed limits.";
         }
         enum CAUSE_THRESHOLD_CROSSED {
           value 16;
           description
             "The limit allowed (or configured) has exceeded.";
         }
         enum PERFORMANCE_DEGRADED {
           value 17;
           description
             "Service limit or service aggrement are outside the acceptable limits.";
         }
	 enum CONGESTION {
           value 18;
           description
             "System is reaching its capacity or approaching it.";
         }
         enum RESOURCE_CREATOR_NEARING_CAPACITY {
           value 19;
           description
             "Probable cause of the alarm is the maximum capacity is already reached or about to be reached.";
         }
         enum STORAGE_CAPACITY_PROBLEM {
           value 20;
           description
             "Probable cause of the alarm is storage capacity problem.";
         }
         enum VERSION_MISMATCH {
           value 21;
           description
             "There is a mismatch in the version of two communicating entities.";
         }
         enum CORRUPT_DATA {
           value 22;
           description
             "An error has caused the data to be incorrect.";
         }
         enum CPU_CYCLES_LIMIT_EXCEEDED {
           value 23;
           description
             "CPU cycles limited has been exceeded its limit.";
         }
	enum SOFTWARE_ERROR {
           value 24;
           description
             "Probable cause of alarm is error in software.";
         }
         enum SOFTWARE_PROGRAM_ERROR {
           value 25;
           description
             "Probable cause of alarm is error in software program error.";
         }
         enum SOFTWARE_PROGRAM_ABNORMALLY_TERMINAGED {
           value 26;
           description
             "Probable cause of alarm is software program abnormally terminated.";
         }
         enum FILE_ERROR {
           value 27;
           description
             "Format of the file is incorrect.";
         }
	 enum OUT_OF_MEMORY {
           value 28;
           description
             "There is no program-addressable storage available.";
         }
         enum UNDERLYING_RESOURCE_UNAVAILABLE {
           value 29;
           description
             "An entity upon which the reporting object depends has become unreliable.";
         }
         enum APPLICATION_SUBSYSTEM_FAILURE {
           value 30;
           description
             "failure is detected in the application subsystem failure. A subsystem can be a software supporting the larger module.";
         }
         enum CONFIGURATION_OR_CUSTOMIZATION_ERROR {
           value 31;
           description
             "The parameter for configuration or customization are given improperly.";
         }
         enum POWER_PROBLEM {
           value 32;
           description
             "There is a problem with the power supply.";
         }
         enum TIMING_PROBLEM {
           value 33;
           description
             "The process which has timing constraints didn't complete with the specified time or has completed but the results are 		      not reliable.";
         }
	 enum PROCESSOR_PROBLEM {
           value 34;
           description
             "Internal machine error has occurred on the a Central processing Unit.";
         }
         enum DATASET_OR_MODEM_ERROR {
           value 35;
           description
             "An internal error has occured on a dataset or modem.";
         }
         enum MULTIPLEXER_PROBLEM {
           value 36;
           description
             "Error occured while multiplexing the communication signal.";
         }
         enum RECEIVER_FAILURE {
           value 37;
           description
             "Probable cause of alarm is receiver failure.";
         }
	 enum TRANSMITTER_FAILURE {
           value 38;
           description
             "Probable cause of alarm is transamitter failure.";
         }
         enum RECEIVE_FAILURE {
           value 39;
           description
             "Probable cause of alarm is receive failure.";
         }
         enum TRANSMIT_FAILURE {
           value 40;
           description
             "Probable cause of alarm is transmission failure.";
         }
         enum OUTPUT_DEVICE_ERROR {
           value 41;
           description
             "Error has occured on a output device.";
         }
         enum INPUT_DEVICE_ERROR {
           value 42;
           description
             "Probable cause of alarm is input device error.";
         }
         enum INPUT_OUTPUT_DEVICE_ERROR {
           value 43;
           description
             "Probable cause of alarm is input output device error.";
         }
	 enum EQUIPMENT_MALFUNCTION {
           value 44;
           description
             "Internal error in equipment malfunction for which no actual cause has been identified.";
         }
         enum ADAPTER_ERROR {
           value 45;
           description
             "Probable cause of alarm is adapter error.";
         }
         enum TEMPERATURE_UNACCEPTABLE {
           value 46;
           description
             "Probable cause of alarm is temperature unacceptable.";
         }
	enum HUMIDITY_UNACCEPTABLE {
           value 47;
           description
             "Probable cause of alarm is humidity unacceptable around equipment.";
         }
         enum HEATING_OR_VENTILATION_OR_COOLING_SYSTEM_PROBLEM {
           value 48;
           description
             "Probable cause of alarm is humidity unacceptable around equipment.";
         }
         enum FIRE_DETECTED {
           value 49;
           description
             "Probable cause of alarm is fire around the equipment.";
         }
         enum FLOOD_DETECTED {
           value 50;
           description
             "Probable cause of alarm is flood around equipment.";
         }
         enum TOXIC_LEAK_DETECTED {
           value 51;
           description
             "Probable cause of alarm is toxic leak is detected around equipment.";
         }
         enum LEAK_DETECTED {
           value 52;
           description
             "A leak of gas or fluid is detected around equipment.";
         }
         enum PRESSURE_UNACCEPTABLE {
           value 53;
           description
             "The fluid or gas pressure is unacceptable.";
         }
	enum EXCESSIVE_VIBRATION {
           value 54;
           description
             "The vibration around the equipment has exceeded the limit.";
         }
         enum MATERIAL_SUPPLY_EXHAUSTED {
           value 55;
           description
             "Probable cause of alarm is exhaustion of the materail supply.";
         }
         enum PUMP_FAILURE {
           value 56;
           description
             "Error has occured in the pump which is used to trasfer fluid in the equipment.";
         }
         enum ENCLOSURE_DOOR_OPEN {
           value 57;
           description
             "Probable cause of alarm is enclosure door is open.";
         }
       }
       description
         "This enumeration defines all the probable causes of the alarm based on the categories";
       reference
         "ITU Recommendation X.736, 'Information Technology - Open Systems Interconnection - System Management:Security Alarm 		  Reporting Function', 1992";
     }

      typedef alarm-rule-relation  {
       type enumeration {
         enum INVALID {
           value 0;
           description
             "There is no valid relation between the alarms (specified in the modeling).";
         } 
         enum NO_RELATION {
           value 1;
           description
             "If there is only one alarm, then there is no relationship
              that must be determined.";
         }
         enum LOGICAL_OR {
           value 2;
           description
             "The alarm is raised or cleared, if at least one of the alarms";
         }
         enum LOGICAL_AND {
           value 3;
           description
             "The alarm is raised or cleared, only if all the alarms (specified in the modeling) exist.";
         }
         
       }
       description
         "If there is only one alarm, then there is no relationship
          that must be determined. If there is more than one alarm,
          then the relationship between them must be determined.
          The relationship can be either a logical OR or
          a logical AND.";
     }
}
